FME workspace Landcover Survey FME.fmw

Parameters:
- GPKG_PATH = D:\AV_lv95\av_2056.gpkg   # "" Select a File

Creator
    GEOMTYPE = Geometry Object
    NUM = 1
    CREATED -> FeatureReader [INITIATOR]
Note: Grundstücke
FeatureReader
    ATTRIBUTES = CSV,"col0,BuKr,WE,Grundstk,""Bez. Grundstück"",L/R,Rg,Ort,PLZ,Straße,Haus-Nr.,E-GRID,Koordinaten,Eigent.art,NuArt1,NuArt2,Mietermod.,GrA,Hist.Gart.,TPF,Gruppe,Verantw.,col22"
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 12
    CSV2_DATE_INPUT_FORMAT = ISO
    CSV2_DELIMITER = <pipe>
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 11
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = D:\260311_Grundstück SAP.txt
    FORMAT = CSV2
    INITIATOR_FIRST_OUTPUT = default
    INTERACT = NONE
    ORDER_RESULTS = No
    OUTPUT_ADD_SCHEMA_ATTRIBUTES = NO
    OUTPUT_FEATURES_DISPLAY = Schema and Data Features
    CSV -> AttributeTrimmer
AttributeTrimmer
    SRC_ATTRS = Bez. Grundstück,BuKr,E-GRID,Eigent.art,GrA,Grundstk,Gruppe,Haus-Nr.,Hist.Gart.,Koordinaten,L/R,Mietermod.,NuArt1,NuArt2,Ort,PLZ,Rg,Straße,TPF,Verantw.,WE,col0,col22
    TRIM_TO_NONE = Yes
    TRIM_TYPE = BOTH
    -> AttributeCreator
AttributeCreator
    ATTR_TABLE:
      SET_TO ID (varchar(200)) = @Value(BuKr)/@Value(WE)/@Value(Grundstk)
      SET_TO Status (varchar(200)) = FME_CONDITIONAL:DEFAULT_VALUE'Gültig'BOOL_OP;OR;COMPOSITE_TEST;1;CASE_INSENSITIVE_TEST @Value(Bez. Grundstück) CONTAINS ABGA'Abgang'BOOL_OP;OR;COMPOSITE_TEST;1;CASE_INSENSITIVE_TEST @Value(Bez. Grundstück) CONTAINS LÖVM        'Löschvermerk'FME_NUM_CONDITIONS3___
      SET_TO Schweiz (varchar(200)) = FME_CONDITIONAL:DEFAULT_VALUE'Ausland'BOOL_OP;OR;COMPOSITE_TEST;1;TEST @Value(L/R) = CH 'Schweiz'FME_NUM_CONDITIONS2___
      SET_TO Eigent.art (uint32) = FME_CONDITIONAL:DEFAULT_VALUE'_FME_NO_OP_'BOOL_OP;OR;COMPOSITE_TEST;1;TEST @Value(Eigent.art) = 1'Eigentum Bund (01)'BOOL_OP;OR;COMPOSITE_TEST;1;TEST @Value(Eigent.art) = 3'Mietobjekt (03)'BOOL_OP;OR;COMPOSITE_TEST;1;TEST @Value(Eigent.art) = 5'Spezialfall (05)'FME_NUM_CONDITIONS4___
      SET_TO TPF (uint32) = FME_CONDITIONAL:DEFAULT_VALUE'_FME_NO_OP_'BOOL_OP;OR;COMPOSITE_TEST;1;TEST @Value(TPF) = 1'Allgemeine Bundesverwaltung (001)'BOOL_OP;OR;COMPOSITE_TEST;1;TEST @Value(TPF) = 2'Ausland (002)'BOOL_OP;OR;COMPOSITE_TEST;1;TEST @Value(TPF) = 3'Zoll (003)'BOOL_OP;OR;COMPOSITE_TEST;1;TEST @Value(TPF) = 4'Gerichte (004)'BOOL_OP;OR;COMPOSITE_TEST;1;TEST @Value(TPF) = 5'Forschungsanstallten (005)'BOOL_OP;OR;COMPOSITE_TEST;1;TEST @Value(TPF) = 6'Kunst und Kultur (006)'BOOL_OP;OR;COMPOSITE_TEST;1;TEST @Value(TPF) = 7'Sport (007)'BOOL_OP;OR;COMPOSITE_TEST;1;TEST @Value(TPF) = 8'Repräsentation Inland (008)'BOOL_OP;OR;COMPOSITE_TEST;1;TEST @Value(TPF) = 9'Infrastruktur (009)'FME_NUM_CONDITIONS10___
      SET_TO Mietermod. (varchar(10)) = FME_CONDITIONAL:DEFAULT_VALUE'_FME_NO_OP_'BOOL_OP;OR;COMPOSITE_TEST;1;TEST @Value(Mietermod.) = 1a'Marktorientiert - Primärgruppe (1a)'BOOL_OP;OR;COMPOSITE_TEST;1;TEST @Value(Mietermod.) = 1b'Marktorientiert - Sekundärgruppe (1b)'BOOL_OP;OR;COMPOSITE_TEST;1;TEST @Value(Mietermod.) = 1c'Marktorientiert - begr. Ausnahmen (1c)'BOOL_OP;OR;COMPOSITE_TEST;1;TEST @Value(Mietermod.) = 2a'Kostenorientiert - Flughafen (2a)'BOOL_OP;OR;COMPOSITE_TEST;1;TEST @Value(Mietermod.) = 2b'Kostenorientiert - zusätz. FLAG (2b)'BOOL_OP;OR;COMPOSITE_TEST;1;TEST @Value(Mietermod.) = 2c'Kostenorientiert mit Integration FLM (2c)'BOOL_OP;OR;COMPOSITE_TEST;1;TEST @Value(Mietermod.) = 3'Zollbauten (3)'BOOL_OP;OR;COMPOSITE_TEST;1;TEST @Value(Mietermod.) = 3a'Zollbauten mit Integration FLM (3a)'BOOL_OP;OR;COMPOSITE_TEST;1;TEST @Value(Mietermod.) = 4'Auslandsbauten EDA (4)'BOOL_OP;OR;COMPOSITE_TEST;1;TEST @Value(Mietermod.) = 4a'Auslandsbauten Wohnen (4a)'BOOL_OP;OR;COMPOSITE_TEST;1;TEST @Value(Mietermod.) = 4b'Auslandsbauten Residenz (4b)'BOOL_OP;OR;COMPOSITE_TEST;1;TEST @Value(Mietermod.) = 4c'Auslandsbauten Kanzlei (4c)'BOOL_OP;OR;COMPOSITE_TEST;1;TEST @Value(Mietermod.) = 4d'Auslandsbauten übrige (4d)'BOOL_OP;OR;COMPOSITE_TEST;1;TEST @Value(Mietermod.) = 5'Keine interne Verrechnung (5)'FME_NUM_CONDITIONS15___
    -> AttributeKeeper
AttributeKeeper
    CREATE_BULK_MODE_FEATURES = NO
    KEEP_ATTRS = Bez. Grundstück,ID,L/R,Ort,PLZ,Rg,Straße,E-GRID,Eigent.art,Koordinaten,Mietermod.,TPF
    -> TestFilter
    -> FeatureJoiner [LEFT]
TestFilter
    DEFAULT_VALUE = <UNFILTERED>
    PASSED_TEST_GROUP_OUTPUT = FIRST
    TEST_LIST = "BOOL_OP,OR,COMPOSITE_TEST,""""""1"""""",TEST_CLAUSE,TEST L/R NOT_ATTRIBUTE_HAS_A_VALUE """,L/R NOT_ATTRIBUTE_HAS_A_VALUE,"BOOL_OP,OR,COMPOSITE_TEST,""""""1"""""",TEST_CLAUSE,TEST @Value(ID) = //",@Value(ID) = //,"BOOL_OP,OR,COMPOSITE_TEST,""""""1"""""",TEST_CLAUSE,TEST @Value(L/R) = CH",@Value(L/R) = CH
    @Value(L/R) = CH -> PythonCaller
Note: Amtliche Vermessung / Grundstück (resf) / Fitler by EGRID
PythonCaller
    PYTHONSOURCE:
      import fme
      import fmeobjects
      import sqlite3

      class FeatureProcessor(object):

          def __init__(self):
              self.egrids = []
              self.incoming = {}
              self.gpkg_path = 'D:/AV_lv95/av_2056.gpkg'
              self.table = 'resf'

          def _gpkg_blob_to_wkb(self, blob):
              """Strip GeoPackage binary header, return WKB as bytearray."""
              if not blob or len(blob) < 8:
                  return None
              if blob[0:2] != b'GP':
                  return bytearray(blob)
              flags = blob[3]
              envelope_type = (flags >> 1) & 0x07
              envelope_sizes = {0: 0, 1: 32, 2: 48, 3: 48, 4: 64}
              header_size = 8 + envelope_sizes.get(envelope_type, 0)
              return bytearray(blob[header_size:])

          def _detect_geom_column(self, cur):
              """Find geometry column by type or common name."""
              cur.execute(f"PRAGMA table_info({self.table})")
              geom_name_candidates = {'geom', 'geometry', 'shape', 'the_geom', 'wkb_geometry'}
              for col in cur.fetchall():
                  col_name = col[1]
                  col_type = col[2].upper()
                  if any(t in col_type for t in ['GEOM', 'POINT', 'POLYGON', 'MULTIPOLYGON', 'LINESTRING', 'BLOB']):
                      return col_name
                  if col_name.lower() in geom_name_candidates:
                      return col_name
              return None

          def input(self, feature):
              egrid = feature.getAttribute('E-GRID')
              if egrid:
                  self.egrids.append(egrid)
                  self.incoming[egrid] = feature.clone()

          def close(self):
              if not self.egrids:
                  return

              conn = sqlite3.connect(self.gpkg_path)
              conn.row_factory = sqlite3.Row
              cur = conn.cursor()

              geom_col = self._detect_geom_column(cur)

              cur.execute(f"PRAGMA table_info({self.table})")
              all_cols = [row[1] for row in cur.fetchall()]
              attr_cols = [c for c in all_cols if c != geom_col]
              col_select = ', '.join([f'm."{c}"' for c in attr_cols])

              print(f"[DEBUG] Table: {self.table}, Geometry column: {geom_col}")
              print(f"[DEBUG] Querying {len(self.egrids)} E-GRIDs")

              placeholders = ','.join(['?' for _ in self.egrids])
              geom_expr = f'm."{geom_col}" AS raw_geometry' if geom_col else 'NULL AS raw_geometry'
              sql = f"""
                  SELECT {col_select}, {geom_expr}
                  FROM "{self.table}" m
                  WHERE "EGRIS_EGRID" IN ({placeholders})
              """
              cur.execute(sql, self.egrids)
              rows = cur.fetchall()
              conn.close()

              print(f"[DEBUG] Rows fetched: {len(rows)}")

              for row in rows:
                  egrid = row['EGRIS_EGRID']

                  # Clone incoming feature to preserve its attributes as base
                  incoming = self.incoming.get(egrid)
                  out = incoming.clone() if incoming else fmeobjects.FMEFeature()

                  # Layer GeoPackage attributes on top
                  for key in attr_cols:
                      val = row[key]
                      if val is not None:
                          out.setAttribute(key, val)

                  # Replace geometry with GeoPackage geometry
                  blob = row['raw_geometry']
                  if blob:
                      wkb = self._gpkg_blob_to_wkb(blob)
                      if wkb:
                          out.importGeometryFromOGCWKB(wkb)

                  self.pyoutput(out)
    PYTHONSYMBOL = FeatureProcessor
    -> AttributeCreator_2
Note: Check_EGRID
AttributeCreator_2
    ATTR_TABLE = SET_TO Check_EGRID (varchar(20)) = EGRID in AV gefunden
    -> CoordinateSystemSetter
Note: To LV95
CoordinateSystemSetter
    COORDSYS = CH1903Plus_1.LV95/01
    -> GeographicAreaCalculator
GeographicAreaCalculator
    AREA_ATTR = area
    AreaMult = 1
    -> BulkAttributeRenamer
    -> FeatureJoiner [RIGHT]
FeatureJoiner
    ATTR_CONFLICT_RES_LOOKUP = USE_LEFT
    GEOMETRY_HANDLING_LOOKUP = USE_LEFT
    JOIN_KEYS = ID ID AUTO
    JOIN_MODE = Left
    ATTR_CONFLICT_RES = Prefer Left
    GEOMETRY_HANDLING = Prefer Left
    JOINED -> AttributeCreator_3
Note: Check_EGRID
AttributeCreator_3
    ATTR_TABLE = SET_TO Check_EGRID (varchar(20)) = FME_CONDITIONAL:DEFAULT_VALUE'EGRID fehlt oder nicht in AV'BOOL_OP;OR;COMPOSITE_TEST;1;TEST Check_EGRID ATTRIBUTE_HAS_A_VALUE _FME_BLANK_STRING_'@Value(Check_EGRID)'FME_NUM_CONDITIONS2___
    -> FeatureWriter [Sheet1]
    -> FeatureWriter_2 [NewFeatureType]
Note: Excel
FeatureWriter
    DATASET = D:\Bodenabdeckung.xlsx
    DATASET_ATTR = _dataset
    FEATURE_TYPE_LIST_ATTR = _feature_types
    FORMAT = XLSXW
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
Note: Prefix GR
BulkAttributeRenamer
    ATTRCHOICE_ACTION = NONPROTECTEDFME
    MODE_CHOICE = RENAME
    PATTERN_ACTION_DISP = ADDPREFIX
    REPLACE_STR = GR_
    ATTRCHOICE = All Attributes
    -> Clipper [CLIPPER]
    -> FeatureReader_2 [INITIATOR]
Note: AV / Bodenabdeckung (lcsf) / Filter by BB intersect
FeatureReader_2
    ATTRIBUTES = cppt,"BFSNr,Kategorie,Nummer,Koordinate,Hoehe,Punktzeichen,Begehbar,Kanton,fid",dprsf,"BFSNr,NBIdent,Nummer,EGRIS_EGRID,Vollstaendigkeit,Art,Flaeche,Gueltigkeit,Kanton,fid",dprsfproj,"BFSNr,NBIdent,Nummer,EGRIS_EGRID,Vollstaendigkeit,Art,Flaeche,Kanton,fid",hadr,"BFSNr,Hausnummer,Gebaeudename,GWR_EGID,GWR_EDID,Strassenname,PLZ,Zusatzziffern,Ortschaftsname,Ori,Loc,Kanton,fid",lcobj,"BFSNr,Typ,Text,Art,Ori,Loc,Kanton,fid",lcsf,"BFSNr,Qualitaet,Art,GWR_EGID,Kanton,fid",lcsfproj,"BFSNr,Qualitaet,Art,GWR_EGID,Kanton,fid",lnna,"BFSNr,Kategorie,Name,Ori,Loc,Kanton,fid",locpos,"BFSNr,Strassenname,Ori,Loc,Kanton,fid",mbsf,"BFSNr,Name,Kanton,fid",osbp,"BFSNr,Gueltigkeit,Punktzeichen,Kanton,fid",osnr,"BFSNr,NBIdent,Nummer,Ori,Loc,Dif,Kanton,fid",osnrproj,"BFSNr,NBIdent,Nummer,Ori,Loc,Dif,Kanton,fid",plli,"BFSNr,Betreiber,Medium,Gueltigkeit,Sichtbarkeit,Kanton,fid",plna,"BFSNr,Betreiber,Ori,Loc,Kanton,fid",plsf,"BFSNr,Betreiber,Medium,Gueltigkeit,Kanton,fid",resf,"BFSNr,NBIdent,Nummer,EGRIS_EGRID,Vollstaendigkeit,Flaeche,Gueltigkeit,Kanton,fid",resfhl,"BFSNr,Kanton,fid",resfproj,"BFSNr,NBIdent,Nummer,EGRIS_EGRID,Vollstaendigkeit,Flaeche,Kanton,fid",slide,"BFSNr,NBIdent,Identifikator,Name,Gueltiger_Eintrag,Kanton,fid",slideobj,"BFSNr,NBIdent,Identifikator,Name,Ori,Loc,Kanton,fid",soli,"BFSNr,Gueltigkeit,Art,Qualitaet,Kanton,fid",soobj,"BFSNr,Typ,Text,Art,Ori,Loc,Kanton,fid",sopt,"BFSNr,Gueltigkeit,Art,Qualitaet,Ori,Kanton,fid",sosf,"BFSNr,Gueltigkeit,Art,Qualitaet,GWR_EGID,Kanton,fid",tbbp,"BFSNr,Gueltigkeit,Punktzeichen,Hoheitsgrenzpunkt,Kanton,fid",tbli,"Typ,Gueltigkeit,Kanton,fid"
    ATTR_ACCUM_MODE = Only Use Result
    CLIP_TO_ENVELOPE = NO
    COMBINE_GEOM = Use Result
    DATASET = D:\AV_lv95\av_2056.gpkg
    FEATURETYPES = lcsf
    FORMAT = OGCGEOPACKAGE
    GEOMETRY_TYPES = cppt,"""wkb_geometry,fme_point""",dprsf,"""wkb_geometry,fme_arc,fme_area,fme_collection,fme_line,fme_point,fme_solid""",dprsfproj,"""wkb_geometry,fme_area""",hadr,"""wkb_geometry,fme_point""",lcobj,"""wkb_geometry,fme_point""",lcsf,"""wkb_geometry,fme_arc,fme_area,fme_collection,fme_line,fme_point,fme_solid""",lcsfproj,"""wkb_geometry,fme_arc,fme_area,fme_collection,fme_line,fme_point,fme_solid""",lnna,"""wkb_geometry,fme_point""",locpos,"""wkb_geometry,fme_point""",mbsf,"""wkb_geometry,fme_area""",osbp,"""wkb_geometry,fme_point""",osnr,"""wkb_geometry,fme_point""",osnrproj,"""wkb_geometry,fme_point""",plli,"""wkb_geometry,fme_line""",plna,"""wkb_geometry,fme_point""",plsf,"""wkb_geometry,fme_area""",resf,"""wkb_geometry,fme_arc,fme_area,fme_collection,fme_line,fme_point,fme_solid""",resfhl,"""wkb_geometry,fme_line""",resfproj,"""wkb_geometry,fme_arc,fme_area,fme_collection,fme_line,fme_point,fme_solid""",slide,"""wkb_geometry,fme_area""",slideobj,"""wkb_geometry,fme_point""",soli,"""wkb_geometry,fme_line""",soobj,"""wkb_geometry,fme_point""",sopt,"""wkb_geometry,fme_point""",sosf,"""wkb_geometry,fme_arc,fme_area,fme_collection,fme_line,fme_point,fme_solid""",tbbp,"""wkb_geometry,fme_point""",tbli,"""wkb_geometry,fme_line"""
    INITIATOR_FIRST_OUTPUT = default
    INTERACT = ENVELOPE_INTERSECTS
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    lcsf -> AttributeKeeper_2
AttributeKeeper_2
    CREATE_BULK_MODE_FEATURES = NO
    KEEP_ATTRS = Art,BFSNr,fid,GWR_EGID
    -> AttributeCreator_4
Note: Check_Grünfläche
AttributeCreator_4
    ATTR_TABLE = SET_TO Check_Grünfläche (varchar(200)) = FME_CONDITIONAL:DEFAULT_VALUE'Keine Grünfläche'BOOL_OP;OR;COMPOSITE_TEST;1;TEST @Value(Art) = Acker_Wiese_Weide'Grünfläche (Hummusiert)'BOOL_OP;OR;COMPOSITE_TEST;1;TEST @Value(Art) = Gartenanlage'Grünfläche (Hummusiert)'BOOL_OP;OR;COMPOSITE_TEST;1;TEST @Value(Art) = geschlossener_Wald'Grünfläche (Bestockt)'BOOL_OP;OR;COMPOSITE_TEST;1;TEST @Value(Art) = Hoch_Flachmoor'Grünfläche (Hummusiert)'BOOL_OP;OR;COMPOSITE_TEST;1;TEST @Value(Art) = Reben'Grünfläche (Hummusiert)'BOOL_OP;OR;COMPOSITE_TEST;1;TEST @Value(Art) = uebrige_bestockte'Grünfläche (Bestockt)'BOOL_OP;OR;COMPOSITE_TEST;1;TEST @Value(Art) = uebrige_humusierte'Grünfläche (Hummusiert)'BOOL_OP;OR;COMPOSITE_TEST;1;TEST @Value(Art) = Wytweide_dicht'Grünfläche (Hummusiert)'BOOL_OP;OR;COMPOSITE_TEST;1;TEST @Value(Art) = Wytweide_offen'Grünfläche (Hummusiert)'FME_NUM_CONDITIONS10___
    -> BulkAttributeRenamer_2
Note: Prefix LC
BulkAttributeRenamer_2
    ATTRCHOICE_ACTION = NONPROTECTEDFME
    MODE_CHOICE = RENAME
    PATTERN_ACTION_DISP = ADDPREFIX
    REPLACE_STR = LC_
    ATTRCHOICE = All Attributes
    -> Clipper [CANDIDATE]
Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Deaggregator
Deaggregator
    ATTR_ACCUM_MODE = HANDLE_CONFLICT
    ATTR_CONFLICT_RES = Use List Attribute Values
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> Dissolver
Dissolver
    ACCUM_INPUT_ATTRS_LOOKUP = One
    CLEANING_TOLERANCE_LOOKUP = AUTO
    CONNECT_Z_MODE_LOOKUP = FIRST_WINS
    DEAGGREGATE_INPUT = Yes
    GROUP_BY = LC_fid
    ACCUM_INPUT_ATTRS = Use Attributes From One Feature
    CLEANING_TOLERANCE = Automatic
    CONNECT_Z_MODE = First Wins
    AREA -> GeographicAreaCalculator_2
    AREA -> PythonCaller_2
GeographicAreaCalculator_2
    AREA_ATTR = _area
    AreaMult = 1
    -> FeatureWriter_2 [Output]
    -> FeatureWriter_3 [Inside]
Note: Excel
FeatureWriter_3
    DATASET = D:\Bodenabdeckung.xlsx
    DATASET_ATTR = _dataset
    FEATURE_TYPE_LIST_ATTR = _feature_types
    FORMAT = XLSXW
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
Note: GeoJSON
FeatureWriter_2
    DATASET = D:\260311_Bodenabdeckung.xlsx
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
Note: Check overlaps
PythonCaller_2 [off]
    PYTHONSOURCE:
      import fme
      import fmeobjects
      from shapely import wkb
      from shapely.strtree import STRtree

      class FeatureProcessor(object):

          def __init__(self):
              self.features = []
              self.min_overlap_m2 = 1.0

          def input(self, feature):
              wkb_bytes = bytes(feature.exportGeometryToOGCWKB())
              if not wkb_bytes:
                  return
              try:
                  geom = wkb.loads(wkb_bytes)
                  if not geom.is_valid:
                      geom = geom.buffer(0)
                  fid = feature.getAttribute('fid') or len(self.features)
                  self.features.append((fid, geom, feature.clone()))
              except Exception as e:
                  print(f"[WARN] Could not parse geometry: {e}")

          def close(self):
              if not self.features:
                  return

              print(f"[DEBUG] Checking {len(self.features)} features for overlaps")

              # Build STRtree spatial index for performance
              geoms = [f[1] for f in self.features]
              tree = STRtree(geoms)

              # Track overlap info per feature index
              # { index: { 'count': int, 'fids': [], 'total_area': float } }
              overlap_info = {i: {'count': 0, 'fids': [], 'total_area': 0.0}
                              for i in range(len(self.features))}

              for i, (fid_a, geom_a, feat_a) in enumerate(self.features):

                  # Only query candidates that intersect bounding box
                  candidate_indices = tree.query(geom_a)

                  for j in candidate_indices:
                      if j <= i:  # Avoid duplicates and self-comparison
                          continue

                      fid_b, geom_b, feat_b = self.features[j]

                      if not geom_a.overlaps(geom_b) and not geom_a.contains(geom_b) and not geom_b.contains(geom_a):
                          continue

                      try:
                          intersection = geom_a.intersection(geom_b)
                      except Exception as e:
                          print(f"[WARN] Intersection failed for {fid_a}/{fid_b}: {e}")
                          continue

                      overlap_area = intersection.area
                      if overlap_area < self.min_overlap_m2:
                          continue

                      print(f"[OVERLAP] fid {fid_a} x fid {fid_b} → {overlap_area:.2f} m²")

                      # Record on both features
                      overlap_info[i]['count'] += 1
                      overlap_info[i]['fids'].append(str(fid_b))
                      overlap_info[i]['total_area'] += overlap_area

                      overlap_info[j]['count'] += 1
                      overlap_info[j]['fids'].append(str(fid_a))
                      overlap_info[j]['total_area'] += overlap_area

              # Output all original features with overlap attributes attached
              for i, (fid, geom, feat) in enumerate(self.features):
                  out = feat.clone()
                  info = overlap_info[i]

                  has_overlap = info['count'] > 0
                  out.setAttribute('overlap_count', info['count'])
                  out.setAttribute('overlap_with_fids', ','.join(info['fids']) if has_overlap else '')
                  out.setAttribute('overlap_total_area_m2', round(info['total_area'], 4))
                  out.setAttribute('has_overlap', 'yes' if has_overlap else 'no')

                  self.pyoutput(out)

              total = sum(1 for i in overlap_info if overlap_info[i]['count'] > 0)
              print(f"[DEBUG] Features with overlaps: {total}")
    PYTHONSYMBOL = FeatureProcessor
    -> AttributeExposer
AttributeExposer
    ATTR_TABLE = has_overlap,,overlap_count,,overlap_total_area_m2,,overlap_with_fids,
